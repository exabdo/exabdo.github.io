(defun c:CVBORDER (/ oucsn oucs ratio cx cy h pll pur)
       
	(if (zerop(getvar 'TILEMODE))
	    (alert "This function is working in Modelspace ONLY")
	    (progn
	        (setvar 'CMDECHO 0)
	        (if (= "" (setq oucsn (getvar 'UCSNAME)))
		    (setq oucs (list (getvar 'UCSORG) (getvar 'UCSXDIR) (getvar 'UCSYDIR)))
		)
	        (command "_.UCS" "_view")
		(setq ratio (/ (nth 0 (getvar "screensize"))(nth 1 (getvar "screensize"))))
		(setq cx (nth 0 (getvar "viewctr")))
		(setq cy (nth 1 (getvar "viewctr")))
		(setq h (getvar "viewsize"))
		(setq pll (list (- cx (/ (* h ratio) 2)) (- cy (/ h 2))))
		(setq pur (list (+ cx (/ (* h ratio) 2)) (+ cy (/ h 2))))
		(command "_.RECTANG" "_non" pll "_non" pur)
	        (if (= "" oucsn)
		    (command "_.UCS" "_non" (nth 0 oucs) "_non" (nth 1 oucs) "_non" (nth 2 oucs))
		    (command "_.UCS" "_named" "_restore" oucsn)
		)
	        (princ "\nDONE!")
	    )
	)
  
  (princ)
)
